module example {
    yang-version 1.1;
    namespace "urn:opendaylight:params:xml:ns:yang:example";
    prefix "example";

    revision "2017-07-25" {
        description "Initial revision of example model";
    }
}
